module packetcable-broker {
    namespace "urn:opendaylight:node:cmts:broker";
    prefix "broker";

    import opendaylight-inventory { prefix inv; revision-date "2013-08-19"; }
    import packetcable-cmts { prefix cmts; revision-date "2014-09-09"; }
    import flow-capable-transaction { prefix tr; }

    description "This module contains a set of notifications to communicate with
        the driver ";
    organization "OpenDaylight Project";

    revision 2014-09-09 {
        description "Initial revision of packetcable broker";
    }
    


    notification cmts-added {
        uses tr:transaction-metadata;
//       uses cmts:cmts-node-attributes;
//       uses cmts:pcmm-apps;
//       uses cmts:pcmm-flow-attributes;
        uses tr:transaction-aware;
    }
    
    notification cmts-updated {
        uses tr:transaction-metadata;
//       uses cmts:cmts-node-attributes;
//       uses cmts:pcmm-apps;
//       uses cmts:pcmm-flow-attributes;
        uses tr:transaction-aware;
    }
    
    notification cmts-removed {
        uses tr:transaction-metadata;
//        uses cmts:cmts-node-attributes;
//        uses cmts:pcmm-apps;
//        uses cmts:pcmm-flow-attributes;
        uses tr:transaction-aware;
    }

      
}
